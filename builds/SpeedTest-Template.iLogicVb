'This file has been auto-generated by Collector version 1.05
'Collection timestamp: 2020/04/06 - 08:28
'2020 Matthew D. Jordan - https://github.com/jordanrobot

'
'</CollectorHeader>
'### SpeedTest ###
'
'https://github.com/jordanrobot/SpeedTest
'MIT license

'Module SpeedTestMain '<CollectorPrepend>'</CollectorPrepend>
    Public Sub Main ()
        
        Dim test As SpeedTest = New SpeedTest()

        test.AddTest("Test One", AddressOf TestOne)
        test.AddTest("Test Two", AddressOf TestTwo)
        test.Iterations = 500
        test.RunTests()
        test.ShowResultsInDialog()

    End Sub

    Public Sub TestOne()
        'Your code here!
    End Sub

    Public Sub TestTwo()
        'Your code here!
    End Sub

'End Module '<CollectorPrepend>'</CollectorPrepend>

Public Class SpeedTest

    Public Delegate Sub CodeToExecute()
    Public Property Iterations As Integer = 1
    Private _results As String = ""
    Private _timers As Dictionary(Of Timer, CodeToExecute) = New Dictionary(Of Timer,CodeToExecute)

    Public Sub New()
    End Sub

    Public Sub AddTest(message As String, ByVal code As CodeToExecute)
        
        _timers.Add(New Timer(message), code)

    End Sub

    Public Sub RunTests()

        For Each timer As KeyValuePair(Of Timer, CodeToExecute) in _timers

           GC.WaitForPendingFinalizers
           GC.Collect

           timer.Key.StartTimer()
           For i = 0 To Iterations
               timer.Value.Invoke()
           Next i
           timer.Key.StopTimer()

           AppendResults(timer.Key.GetResults)
       Next timer
    End Sub

    Public Sub ShowResultsInDialog()
        System.Windows.Forms.Messagebox.Show(_results)
    End Sub

    Public Function GetResults() As String
        Return _results
    End Function

    Private Sub AppendResults(value As String)
        _results = _results & vbLf & value
    End Sub

End Class

Public Class Timer

    Private _stopwatch As Stopwatch = New Stopwatch()
    Private _timespan As TimeSpan
    Private _totalTime As String
    Private _message As String = ""
    Private _result As String = "Speed test has not been run."

    Public Sub New()
    End Sub

    Public Sub New(value As String)
        me._message = value
    End Sub

    Public Sub StartTimer()
        _stopwatch.Start()
    End Sub

    Public Sub StopTimer()
        _stopwatch.Stop()
        _timespan = _stopwatch.Elapsed
        _result = String.Format("{0:00}.{1:000} seconds", (_timespan.Hours * 3600) + (_timespan.Minutes*60) + _timespan.Seconds, _timespan.Milliseconds)
    End Sub

    Public Function GetResults() As String
        Return me._message & " Total Time: " & _result
    End Function

    Public Function GetMessage() As String
        Return me._message
    End Function
End Class
